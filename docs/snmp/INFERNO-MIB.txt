-- INFERNO-MIB
-- Inferno AoIP Appliance private enterprise MIB
-- Enterprise OID arc: .1.3.6.1.4.1.99999
-- Import into your NMS to resolve Inferno custom OIDs.

INFERNO-MIB DEFINITIONS ::= BEGIN

IMPORTS
    MODULE-IDENTITY, OBJECT-TYPE, Integer32, Unsigned32,
    enterprises                     FROM SNMPv2-SMI
    DisplayString                   FROM SNMPv2-TC;

infernoMIB MODULE-IDENTITY
    LAST-UPDATED "202604100000Z"
    ORGANIZATION "Inferno AoIP Project"
    CONTACT-INFO "legopc/inferno-aoip-releases"
    DESCRIPTION  "Inferno AoIP Appliance monitoring MIB"
    REVISION     "202604100000Z"
    DESCRIPTION  "Initial version"
    ::= { enterprises 99999 }

inferno OBJECT IDENTIFIER ::= { infernoMIB 1 }

infernoMode OBJECT-TYPE
    SYNTAX      DisplayString
    MAX-ACCESS  read-only
    STATUS      current
    DESCRIPTION "Current appliance mode (spotify|aux-in|aux-out|aux-bidir|iradio)"
    ::= { inferno 1 }

infernoVersion OBJECT-TYPE
    SYNTAX      DisplayString
    MAX-ACCESS  read-only
    STATUS      current
    DESCRIPTION "Appliance image version string"
    ::= { inferno 2 }

infernoPtpState OBJECT-TYPE
    SYNTAX      DisplayString
    MAX-ACCESS  read-only
    STATUS      current
    DESCRIPTION "PTP clock synchronisation state (locked|acquiring|unknown)"
    ::= { inferno 3 }

infernoDanteState OBJECT-TYPE
    SYNTAX      DisplayString
    MAX-ACCESS  read-only
    STATUS      current
    DESCRIPTION "inferno-bridge (Dante TX) systemd service state"
    ::= { inferno 4 }

infernoLibreState OBJECT-TYPE
    SYNTAX      DisplayString
    MAX-ACCESS  read-only
    STATUS      current
    DESCRIPTION "librespot (Spotify Connect) systemd service state"
    ::= { inferno 5 }

infernoUptime OBJECT-TYPE
    SYNTAX      Unsigned32
    UNITS       "seconds"
    MAX-ACCESS  read-only
    STATUS      current
    DESCRIPTION "System uptime in seconds"
    ::= { inferno 6 }

infernoHostname OBJECT-TYPE
    SYNTAX      DisplayString
    MAX-ACCESS  read-only
    STATUS      current
    DESCRIPTION "System hostname"
    ::= { inferno 7 }

infernoPtpOffset OBJECT-TYPE
    SYNTAX      Integer32
    UNITS       "nanoseconds"
    MAX-ACCESS  read-only
    STATUS      current
    DESCRIPTION "PTP offset from master clock in nanoseconds"
    ::= { inferno 8 }

infernoSoundcard OBJECT-TYPE
    SYNTAX      DisplayString
    MAX-ACCESS  read-only
    STATUS      current
    DESCRIPTION "Primary ALSA soundcard name"
    ::= { inferno 9 }

END
